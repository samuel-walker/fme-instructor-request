FME workspace CallGeocoder.fmw

Parameters:
- AddressAttr = AddressLine1   # Address
- CityAttr = City   # City
- ProvinceAttr = StateProvince   # Province/State
- PostalCodeAttr =   # Postal Code/Zip
- CountryAttr =   # Country
- SourceDataset = /www/fmepedia-easygeocoder/fme/data/TestFile_1000.csv   # Source Comma Separated Value (CSV) File(s)

Readers:
- CSV_1: CSV from $(SourceDataset)

Writers:
- OGCKML_1: OGCKML to /www/fmepedia-easygeocoder/fme/data/Output/GeocodedResults.kml

Note: Read uploaded CSV file from user. / Reader is restricted to a maximum / of 50 records.
CSV (reader CSV_1)
    attributes: RecordID number(5,0), acct_sgmnt_cd char(9), lblty_type_cd char(4), AddressLine1 char(39), addr2 char(19), City char(19), StateProvince char(3), PostalCode number(6,0), zip4 number(5,0), act_susp_lines number(3,0)
    -> AttributeCreator
AttributeCreator
    ATTR_LIST = _addr,"FME_CONDITIONAL:DEFAULT_VALUE'@Value($(AddressAttr))'BOOL_OP;OR;COMPOSITE_TEST;<Unused>;TEST $(AddressAttr) ATTRIBUTE_IS_EMPTY _FME_BLANK_STRING_;TEST $(AddressAttr) ATTRIBUTE_IS_MISSING _FME_BLANK_STRING_''FME_NUM_CONDITIONS2___",_postal,"FME_CONDITIONAL:DEFAULT_VALUE'@Value($(PostalCodeAttr))'BOOL_OP;OR;COMPOSITE_TEST;<Unused>;TEST $(PostalCodeAttr) ATTRIBUTE_IS_EMPTY _FME_BLANK_STRING_;TEST $(PostalCodeAttr) ATTRIBUTE_IS_MISSING _FME_BLANK_STRING_''FME_NUM_CONDITIONS2___",_country,"FME_CONDITIONAL:DEFAULT_VALUE'@Value($(CountryAttr))'BOOL_OP;OR;COMPOSITE_TEST;<Unused>;TEST $(CountryAttr) ATTRIBUTE_IS_MISSING _FME_BLANK_STRING_;TEST $(CountryAttr) ATTRIBUTE_IS_EMPTY _FME_BLANK_STRING_''FME_NUM_CONDITIONS2___",_city,"FME_CONDITIONAL:DEFAULT_VALUE'@Value($(CityAttr))'BOOL_OP;OR;COMPOSITE_TEST;<Unused>;TEST $(CityAttr) ATTRIBUTE_IS_EMPTY _FME_BLANK_STRING_;TEST $(CityAttr) ATTRIBUTE_IS_MISSING _FME_BLANK_STRING_''FME_NUM_CONDITIONS2___",_province,"FME_CONDITIONAL:DEFAULT_VALUE'@Value($(ProvinceAttr))'BOOL_OP;OR;COMPOSITE_TEST;<Unused>;TEST $(ProvinceAttr) ATTRIBUTE_IS_EMPTY _FME_BLANK_STRING_;TEST $(ProvinceAttr) ATTRIBUTE_IS_MISSING _FME_BLANK_STRING_''FME_NUM_CONDITIONS2___"
    -> GoogleGeocoder
GoogleGeocoder
    State = @Value(_province)
    Street_Address = @Value(_addr)
    Country = @Value(_country)
    MapsAPI = http://maps.googleapis.com
    City = @Value(_city)
    mode = No
    Postal_Code = @Value(_postal)
    GeocodeFormat = Discrete attributes
    Geocoded -> NewFeatureType (writer OGCKML_1)
    Not_Geocoded -> Terminator
NewFeatureType (writer OGCKML_1)
Terminator
    MESSAGE:
      There was an error geocoding one or more of your addresses.

      Message: "@Value(_error)"

FME custom transformer GoogleGeocoder
This transformer uses the google geocoder to identify the positiion of addresses on the earth. You can either use it as a regular user or enter your Google Maps for business Client ID and Key.
Select whether you want to use a freeform address or discrete fields. Discrete fields are concatenated as follows, and the result is identical to manual concatenation of attribute values:
Street Address, City, State, Postal Code, Country
If you want to use a Google Maps for Business key, set the "Using Google Maps for Business key" parameter to yes and enter your Client ID and Key in the "Cliend ID" and "Crypto Key" parameters.
Please Note: Usage Limits (from https://developers.google.com/maps/documentation/geocoding/)
Use of the Google Geocoding API is subject to a query limit of 2,500 geolocation requests per day. (Users of Google Maps API for Business may perform up to 100,000 requests per day.) This limit is enforced to prevent abuse and/or repurposing of the Geocoding API, and this limit may be changed in the future without notice. Additionally, Google enforces a request rate limit to prevent abuse of the service. If you exceed the 24-hour limit or otherwise abuse the service, the Geocoding API may stop working for you temporarily. If you continue to exceed this limit, your access to the Geocoding API may be blocked.
Note: the Geocoding API may only be used in conjunction with a Google map; geocoding results without displaying them on a Google Map is prohibited. For complete details on allowed usage, consult the Maps API Terms of Service License Restrictions.
So be sure to send the results through a StaticMapOverlayer afterwards!
    Copyright (c) 2014 Safe Software Inc.
Permission is granted to anyone, free of charge, to use, modify and distribute the object code form of this transformer for any purpose, subject to the following restrictions:
1) The origin of this transformer and associated FME software must not be misrepresented.
2) This transformer may only be used in conjunction with a validly licensed copy of FME software.
3) The Google Geocoder service is copyrighted by Google. Please visit "http://developers.google.com/maps/documentation/geocoding" for more information.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- GeocodeFormat = Freeform   # attributes,FullAddress" Address format
- FullAddress = <Unused>   # Freeform address
- Street_Address =   # Street address
- City =
- State =
- Postal_Code =   # Postal Code
- Country =
- mode = No   # Using a Google Maps for Business key
- clientid =   # Client ID
- cryptokey =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   # Crypto Key
- MapsAPI = http://maps.googleapis.com   # Maps API Url

Input (input)
    -> AttributeCreator_2
Geocoded (output)
Not_Geocoded (output)

Bookmark: General geocoding prep
Note: Add all necessary / attributes
AttributeCreator_2
    ATTR_LIST = GG_StrAdd,$(Street_Address),GG_City,$(City),GG_State,$(State),GG_PCode,$(Postal_Code),GG_Country,$(Country)
    -> AttributeCreator_3
Note: Select appropriate full address / depending on format
AttributeCreator_3
    ATTR_LIST = GG_FullAddress,"FME_CONDITIONAL:DEFAULT_VALUE'@Value(GG_StrAdd),@Value(GG_City),@Value(GG_State),@Value(GG_PCode),@Value(GG_Country)'BOOL_OP;OR;COMPOSITE_TEST;<Unused>;TEST $(GeocodeFormat) = Freeform'$(FullAddress)'FME_NUM_CONDITIONS2___"
    -> PythonCaller_2
Note: Make sure address / is URL encoded
PythonCaller_2
    PYTHONSOURCE:
      import fmeobjects,urllib

      # Template Function interface:
      def processFeature(feature):

          # Make sure all address attributes are URL safe
          streetaddress = urllib.quote_plus(str(feature.getAttribute("GG_StrAdd")))
          feature.setAttribute("GG_StrAdd",streetaddress)
          streetaddress = urllib.quote_plus(str(feature.getAttribute("GG_City")))
          feature.setAttribute("GG_City",streetaddress)
          streetaddress = urllib.quote_plus(str(feature.getAttribute("GG_State")))
          feature.setAttribute("GG_State",streetaddress)
          streetaddress = urllib.quote_plus(str(feature.getAttribute("GG_PCode")))
          feature.setAttribute("GG_PCode",streetaddress)
          streetaddress = urllib.quote_plus(str(feature.getAttribute("GG_Country")))
          feature.setAttribute("GG_Country",streetaddress)
    PYTHONSYMBOL = processFeature
    -> BuildURL_2
Note: Build URL part needed for / creating Digital Signature
BuildURL_2: StringConcatenator
    PARM_LINE = /maps/api/geocode/json?address=@Value(GG_FullAddress)&sensor=false
    VAL_ATTR = URLtoSign
    -> Tester

Bookmark: Google Geocoder
Note: Detemine if user wants to / use Maps for Business key
Tester
    TEST_MODE = Automatic
    TEST_DESCRIPTION = ""
    BOOL_OP = OR
    TEST_CLAUSE = TEST $(mode) = No
    FAILED -> StringConcatenator
    PASSED -> BuildURL_4
Note: HTTP Call has failed. Check the _http_status_code and _error attributes on the feature
AttributeRemover_2
    LIST_ATTRS = _headers{}.value _headers{}.name _headers{}
    REMOVE_ATTRS = googleGeocodeURL,GG_StrAdd,GG_City,GG_State,GG_PCode,GG_Country,cryptokey,encodedsignature,URLtoSign,geocode_json
    -> Not_Geocoded (output)

Bookmark: Prepare for Geocoding without user key
Note: Build Complete / URL for request
BuildURL_4: StringConcatenator
    PARM_LINE = $(MapsAPI)@Value(URLtoSign)
    VAL_ATTR = googleGeocodeURL
    -> GoogleGeocode

Bookmark: Prepare for Geocoding with user key
Note: Add clientid
StringConcatenator
    PARM_LINE = @Value(URLtoSign)&client=$(clientid)
    VAL_ATTR = URLToSign
    -> AttributeCreator
Note: Add cryptokey
AttributeCreator
    ATTR_LIST = crpytokey,$(cryptokey),encodedsignature,""
    -> PythonCaller
Note: Create Digital Signature
PythonCaller
    PYTHONSOURCE:
      import fmeobjects,base64,hashlib,hmac

      # Template Function interface:
      def processFeature(feature):

          # Get the key value and decode it
          cryptokey = feature.getAttribute('cryptokey')
          decodedKey = base64.urlsafe_b64decode(str(cryptokey))

          # Create Digital Signature for the request - Different requests need different signatures
          urltosign = feature.getAttribute('URLtoSign')
          signature = hmac.new(decodedKey,urltosign,hashlib.sha1)

          # Encode the Digital Signature and return it as an attribute value
          encodedsign = base64.urlsafe_b64encode(signature.digest())
          feature.setAttribute('encodedsignature',encodedsign)
    PYTHONSYMBOL = processFeature
    -> BuildURL_3
Note: Build Complete / URL for request
BuildURL_3: StringConcatenator
    PARM_LINE = $(MapsAPI)@Value(URLtoSign)&signature=@Value(encodedsignature)
    VAL_ATTR = googleGeocodeURL
    -> GoogleGeocode

Bookmark: Geocode
Note: Invoke Google Geocoder
GoogleGeocode: HTTPFetcher
    TARGET_URL = @Value(googleGeocodeURL)
    STATUS_CODE_ATTR = _http_status_code
    SAVE_FILE = No
    PROXY_AUTH_METHOD = Basic
    RESPONSE_HEADER_LIST_ATTR = _headers
    ERROR_ATTR = _error
    USE_COOKIES = No
    AUTH_METHOD = Basic
    TARGET_ATTR = geocode_json
    -> JSONFlattener
    <REJECTED> -> AttributeRemover_2

Bookmark: Decode Google Geocode
Note: Flatten The returned JSON / and create attributes
JSONFlattener
    RECURSIVE = Yes
    JSON_ATTR = geocode_json
    -> BulkAttributeRenamer_2
Note: Unwrap the results group / from the first group inside it
BulkAttributeRenamer_2
    REPLACE_STR = results{0}.
    ATTRCHOICE = All Attributes
    PATTERN_ACTION_DISP = Remove Prefix String
    CASE_DISP = yes
    -> BulkAttributeRenamer
Note: Remove the / "geometry." prefix
BulkAttributeRenamer
    REPLACE_STR = geometry.
    ATTRCHOICE = All Attributes
    PATTERN_ACTION_DISP = Remove Prefix String
    CASE_DISP = yes
    -> AttributeExposer
Note: Expose attributes
AttributeExposer
    ATTR_LIST = location.lat,location.lng,location_type,formatted_address,bounds.northeast.lat,bounds.northeast.lng,bounds.southwest.lat,bounds.southwest.lng,status,address_components{}
    -> 2DPointReplacer
Note: Replace the feature with a / point at returned Lat/Long
2DPointReplacer
    XVALATTR = @Value(location.lng)
    YVALATTR = @Value(location.lat)
    POINT -> AttributeRemover
Note: Remote Extra attributes
AttributeRemover
    LIST_ATTRS = _headers{}.value _headers{}.name _headers{} address_components{}
    REMOVE_ATTRS = googleGeocodeURL,GG_StrAdd,GG_City,GG_State,GG_PCode,GG_Country,cryptokey,encodedsignature,URLtoSign,_error,geocode_json
    -> TestFilter
Note: Check whether Geocoding / has been successful
TestFilter
    TEST_LIST = BOOL_OP,OR,COMPOSITE_TEST,<Unused>,TEST_CLAUSE,"TEST @Value(status) = OK",Geocoded
    DEFAULT_VALUE = Not Geocoded
    Geocoded -> CoordinateSystemSetter
    Not Geocoded -> Not_Geocoded (output)
Note: set coordinate system
CoordinateSystemSetter
    COORDSYS = LL84
    -> Geocoded (output)
